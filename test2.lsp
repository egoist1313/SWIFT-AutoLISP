(defun C:PAIRSWAP (/ ss i pts en ed pt_ucs x y pair pt1 pt2 swA swB standing dA dB chosen)
  ;; 1. Выбор точек (все координаты переводим в текущую ПСК)
  (setq ss (ssget '((0 . "POINT"))))
  (if (not ss)
    (progn (princ "\nНе выбрано ни одной точки.") (exit))
  )

  ;; 2. Сбор UCS-координат исходных точек (X Y)
  (setq i 0 pts '())
  (repeat (sslength ss)
    (setq en     (ssname ss i)
          ed     (entget en)
          pt_ucs (trans (cdr (assoc 10 ed)) 0 1)  ; WCS -> UCS
          x      (car pt_ucs)
          y      (cadr pt_ucs)
          i      (1+ i))
    (setq pts (cons (list x y) pts))               ; список (X Y) в UCS
  )

  ;; 3. Жадное разбиение на пары ближайших друг к другу точек (в UCS)
  (setq pairs '())
  (while (>= (length pts) 2)
    (setq minDist 1e+99 minI nil minJ nil)
    (setq n (length pts) i 0)
    (while (< i (1- n))
      (setq j (1+ i))
      (while (< j n)
        (if (< (setq d (distance (nth i pts) (nth j pts))) minDist)
          (setq minDist d minI i minJ j)
        )
        (setq j (1+ j))
      )
      (setq i (1+ i))
    )
    (setq pair (list (nth minI pts) (nth minJ pts))
          pairs (cons pair pairs))
    ;; удаление использованных точек
    (setq newPts '() i 0)
    (while (< i n)
      (if (and (/= i minI) (/= i minJ))
        (setq newPts (cons (nth i pts) newPts))
      )
      (setq i (1+ i))
    )
    (setq pts (reverse newPts))
  )

  (if (not pairs)
    (progn (princ "\nСлишком мало точек для формирования пар.") (exit))
  )

  ;; 4. Запрос точки стоянки (в текущей ПСК)
  (setq standing (getpoint "\nУкажите точку стоянки: "))
  (if (not standing)
    (progn (princ "\nТочка стоянки не указана.") (exit))
  )
  ;; getpoint уже возвращает координаты в ПСК, оставляем только X,Y
  (setq standing (list (car standing) (cadr standing)))

  ;; 5. Перекрёстные варианты и выбор ближайшей к стоянке
  (setq finalPts_ucs '())
  (foreach pair pairs
    (setq pt1 (car pair)
          pt2 (cadr pair))
    ;; A = (X1, Y2)   B = (X2, Y1)   (всё в UCS)
    (setq swA (list (car pt1) (cadr pt2))
          swB (list (car pt2) (cadr pt1))
          dA  (distance standing swA)
          dB  (distance standing swB))
    (if (<= dA dB)
      (setq chosen swA)
      (setq chosen swB)
    )
    (setq finalPts_ucs (cons chosen finalPts_ucs))
  )

  ;; 6. Создание результирующих точек (переводим обратно в WCS для entmake)
  (foreach pt_ucs (reverse finalPts_ucs)
    (entmake
      (list
        '(0 . "POINT")
        (cons 10 (trans (list (car pt_ucs) (cadr pt_ucs) 0.0) 1 0)) ; UCS -> WCS
      )
    )
  )

  (princ (strcat "\nСоздано точек: " (itoa (length finalPts_ucs))))
  (princ)
)
