; SWIFT-START
(vl-load-com)
(defun _rp-safe-get (obj propname / val)
  (if (vlax-property-available-p obj propname)
    (progn
      (setq val (vlax-get-property obj propname))
      (if (= (type val) 'VARIANT) (vlax-variant-value val) val))
    nil))
(defun _rp-get-vla (obj propname / res)
  (setq res (vl-catch-all-apply 'vlax-get-property (list obj propname)))
  (if (vl-catch-all-error-p res) nil res))
(defun _rp-reverse-one (obj / name startPt endPt sElev eElev sInvert eInvert sStruct eStruct)
  (if (/= (vla-get-ObjectName obj) "AeccDbPipe")
    nil
    (progn
      (setq name    (vlax-get-property obj 'Name))
      (if (null name) (setq name "без имени"))
      ;; PointAtParam вместо StartPoint/EndPoint — те возвращают (0,0,0)
      (setq startPt (vlax-get-property obj 'PointAtParam 0)
            endPt   (vlax-get-property obj 'PointAtParam 1)
            sElev   (_rp-safe-get obj "StartCenterlineElevation")
            eElev   (_rp-safe-get obj "EndCenterlineElevation")
            sInvert (_rp-safe-get obj "StartInvertElevation")
            eInvert (_rp-safe-get obj "EndInvertElevation")
            sStruct (_rp-get-vla obj 'StartStructure)
            eStruct (_rp-get-vla obj 'EndStructure))
      ;; Отключить от колодцев (0=Start, 1=End)
      (vl-catch-all-apply 'vlax-invoke-method (list obj 'Disconnect 0))
      (vl-catch-all-apply 'vlax-invoke-method (list obj 'Disconnect 1))
      ;; Развернуть геометрию
      (vlax-invoke-method obj 'SetStartandEndPoints endPt startPt)
      ;; Восстановить отметки
      (if (and sElev eElev)
        (progn
          (vlax-put-property obj 'StartCenterlineElevation eElev)
          (vlax-put-property obj 'EndCenterlineElevation   sElev)))
      (if (and sInvert eInvert)
        (progn
          (vlax-put-property obj 'StartInvertElevation eInvert)
          (vlax-put-property obj 'EndInvertElevation   sInvert)))
      ;; Подключить в обратном порядке: бывший конец \U+2192 начало, бывшее начало \U+2192 конец
      (if eStruct (vl-catch-all-apply 'vlax-invoke-method (list obj 'ConnectToStructure 0 eStruct)))
      (if sStruct (vl-catch-all-apply 'vlax-invoke-method (list obj 'ConnectToStructure 1 sStruct)))
      (vla-update obj)
      (princ (strcat "\n[OK] " name))
      t)))
(defun C:REVERSEPIPE (/ *error* selSS i obj count old_osmode)
  (defun *error* (msg)
    (if old_osmode (setvar "OSMODE" old_osmode))
    (if (and msg (not (wcmatch (strcase msg) "*CANCEL*,*QUIT*,*EXIT*")))
      (princ (strcat "\nОшибка REVERSEPIPE: " msg)))
    (princ))
  (setq old_osmode (getvar "OSMODE"))
  (setvar "OSMODE" 0)
  (princ "\n=== Разворот труб (Civil 3D) ===")
  (princ "\nВыберите трубы для разворота. Enter — отменить.\n")
  (if (not (setq selSS (ssget '((0 . "AECC_PIPE")))))
    (progn (setvar "OSMODE" old_osmode) (princ "\n[!] Трубы не выбраны.") (princ) (exit)))
  (setq i 0 count 0)
  (repeat (sslength selSS)
    (setq obj (vlax-ename->vla-object (ssname selSS i)))
    (if (_rp-reverse-one obj) (setq count (1+ count)))
    (setq i (1+ i)))
  (princ (strcat "\n\nГотово! Развёрнуто " (itoa count) " труб(ы)."))
  (princ "\nПроверьте сеть и обновите профили.")
  (setvar "OSMODE" old_osmode)
  (princ))
(defun C:RT ()       (C:REVERSEPIPE))
(defun C:РАЗВОРОТ () (C:REVERSEPIPE))
(princ "\nКоманды: REVERSEPIPE / RT / РАЗВОРОТ")
(princ)
; SWIFT-END
