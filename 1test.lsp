(vl-load-com)

(defun c:АБРАКАДАБРА ( / ss i blkref atts att txt ip h rot lay sty lt lts oldcmd ent textobj exploded)
  (setq oldcmd (getvar "CMDECHO"))
  (setvar "CMDECHO" 0)
  (if (setq ss (ssget "_:L" '((0 . "INSERT"))))
    (progn
      (setq i -1)
      (repeat (sslength ss)
        (setq i (1+ i))
        (setq blkref (vlax-ename->vla-object (ssname ss i)))
        (if (and (vlax-property-available-p blkref 'HasAttributes)
                 (eq :vlax-true (vla-get-HasAttributes blkref)))
          (progn
            (setq atts (vlax-safearray->list (vlax-variant-value (vla-GetAttributes blkref))))
            (foreach att atts
              (if (eq :vlax-true (vla-get-Visible att))
                (progn
                  (setq txt  (vla-get-TextString att)
                        ip   (vlax-safearray->list (vlax-variant-value (vla-get-InsertionPoint att)))
                        h    (vla-get-Height att)
                        rot  (vla-get-Rotation att)
                        lay  (vla-get-Layer att)
                        sty  (vla-get-StyleName att)
                        lt   (vla-get-Linetype att)
                        lts  (vla-get-LinetypeScale att))
                  (command-s "_.TEXT" "_non" ip h (angtos rot 0 8) txt)
                  (if (setq ent (entlast))
                    (progn
                      (entmod (subst (cons 8 lay) (assoc 8 (entget ent)) (entget ent)))
                      (setq textobj (vlax-ename->vla-object ent))
                      (vla-put-Color textobj (vla-get-Color att))
                      (vla-put-TrueColor textobj (vla-get-TrueColor att))
                      (if (and lt (/= lt "BYLAYER") (/= lt "BYBLOCK"))
                        (vla-put-Linetype textobj lt))
                      (vla-put-LinetypeScale textobj lts)
                      (if (/= sty "Standard")
                        (vla-put-StyleName textobj sty))
                      (entupd ent)
                    )
                  )
                )
              )
            )
            (command "_.REGEN")
            (command "_.DELAY" 400)
          )
        )
        (setq exploded (vl-catch-all-apply 'vla-Explode (list blkref)))
        (if (vl-catch-all-error-p exploded)
          (command-s "_.EXPLODE" (vlax-vla-object->ename blkref) "")
          (vla-Delete blkref)
        )
        (command "_.DELAY" 200)
      )
    )
  )
  (setvar "CMDECHO" oldcmd)
  (princ)
)
